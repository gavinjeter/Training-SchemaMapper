FME workspace SchemaMapper.fmw

Creator
    GEOMTYPE = Geometry Object
    NUM = 10000
    CREATED -> RandomNumberGenerator
Note: Create randomized values
RandomNumberGenerator
    MAX = 40
    MIN = 1
    PLACES = 0
    RESULT_ATTR = value
    -> AttributeCreator
Note: Create distinct attributes
AttributeCreator
    ATTR_TABLE:
      SET_TO active (varchar(200)) = FME_CONDITIONAL:DEFAULT_VALUE'active'BOOL_OP;OR;COMPOSITE_TEST;1 OR 2;CASE_INSENSITIVE_TEST @Evaluate(@Value(value)/2) ENDS_WITH 0.5;CASE_INSENSITIVE_TEST @Evaluate(@Value(value)/2) ENDS_WITH 5.5'inactive'FME_NUM_CONDITIONS2___
      SET_TO status (varchar(200)) = FME_CONDITIONAL:DEFAULT_VALUE'complete'BOOL_OP;OR;COMPOSITE_TEST;1;CASE_INSENSITIVE_TEST @Evaluate(@Value(value)/3) CONTAINS .33'incomplete'BOOL_OP;OR;COMPOSITE_TEST;1;CASE_INSENSITIVE_TEST @Evaluate(@Value(value)/3) CONTAINS .66'repair'FME_NUM_CONDITIONS3___
      SET_TO shape (varchar(200)) = FME_CONDITIONAL:DEFAULT_VALUE'star'BOOL_OP;OR;COMPOSITE_TEST;1;CASE_INSENSITIVE_TEST @Evaluate(@Value(value)/4) ENDS_WITH .25'square'BOOL_OP;OR;COMPOSITE_TEST;1;CASE_INSENSITIVE_TEST @Evaluate(@Value(value)/4) ENDS_WITH .5'circle'BOOL_OP;OR;COMPOSITE_TEST;1;CASE_INSENSITIVE_TEST @Evaluate(@Value(value)/4) ENDS_WITH .75'triangle'FME_NUM_CONDITIONS4___
      SET_TO color (varchar(200)) = FME_CONDITIONAL:DEFAULT_VALUE'yellow'BOOL_OP;OR;COMPOSITE_TEST;1;CASE_INSENSITIVE_TEST @Evaluate(@Value(value)/5) ENDS_WITH .2'black'BOOL_OP;OR;COMPOSITE_TEST;1;CASE_INSENSITIVE_TEST @Evaluate(@Value(value)/5) ENDS_WITH .4'blue'BOOL_OP;OR;COMPOSITE_TEST;1;CASE_INSENSITIVE_TEST @Evaluate(@Value(value)/5) ENDS_WITH .6'green'BOOL_OP;OR;COMPOSITE_TEST;1;CASE_INSENSITIVE_TEST @Evaluate(@Value(value)/5) ENDS_WITH .8'red'FME_NUM_CONDITIONS5___
    -> SchemaMapper
Note: SchemaMapper_DataMapping.xlsx / Map features to category using SchemaMapper
SchemaMapper
    DATASET = $(FME_MF_DIR_USERTYPED)SchemaMapper_DataMapping.xlsx
    FORMAT = XLSXR
    IDXDESTATTR = fme_feature_type
    IDXDESTCOL = ""
    IDXSOURCEATTR = fme_feature_type
    IDXSOURCECOL = ""
    MAP_ATTRS = """""" output_field output_value
    MATCH_ATTRS = input_field_1 input_value_1$(FME_ASC_16) input_field_2 input_value_2$(FME_ASC_16) input_field_3 input_value_3$(FME_ASC_16) input_field_4 input_value_4$(FME_ASC_16)
    ROW_ID_ATTR = _schemamapper_row_ids
    TABLE = Sheet1
    XLSXR_ALLOW_DOLLAR_SIGNS = YES
    XLSXR_APPLY_FILTERS = No
    XLSXR_CASE_SENSITIVE_FEATURE_TYPES = YES
    XLSXR_CONFIGURATION_DATASET = $(FME_MF_DIR)SchemaMapper_DataMapping.xlsx
    XLSXR_CREATE_FEATURE_TABLES_FROM_DATA = Yes
    XLSXR_EXCEL_COL_NAMES = YES
    XLSXR_EXPANDED_DATES_SCANNING = No
    XLSXR_EXPAND_MERGED_CELLS = Yes
    XLSXR_FORCE_DATETIME = NO
    XLSXR_QUERY_FEATURE_TYPES_FOR_MERGE_FILTERS = Yes
    XLSXR_READ_BLANK_AS = Null
    XLSXR_READ_FORM_CONTROLS = NONE
    XLSXR_READ_RASTER_MODE = None
    XLSXR_REPLACE_ONLY_NEWLINES_CARRIAGE_RETURNS = YES
    XLSXR_SCAN_FOR_GEOMETRIC_TYPES = Yes
    XLSXR_SCAN_MAX_FEATURES = 1000
    XLSXR_SCHEMA = Sheet1,0,input_field_1,char,6,,,1,input_value_1,char,6,,,2,input_field_2,char,6,,,3,input_value_2,char,8,,,4,input_field_3,char,5,,,5,input_value_3,char,4,,,6,input_field_4,char,5,,,7,input_value_4,char,6,,,8,output_field,char,8,,,9,output_value,char,13,,,1,,,,NO,NO,1,C:\Users\Gavin\Documents\FME\Repositories\Training-SchemaMapper\SchemaMapper_DataMapping.xlsx,"0,0,9,8",,NO,NO
    XLSXR_SCHEMA_HANDLING_REVISION = 2
    XLSXR_SKIP_EMPTY_ROWS = YES
    XLSXR_STRIP_SHEETNAME_SPACES = YES
    XLSXR_TABLELIST = Sheet1
    XLSXR_TRIM_ATTR_NAME_WHITESPACE = Yes
    XLSXR_USE_CUSTOM_SCHEMA = NO
    MAPPED -> AttributeExposer
Note: Expose Category field
AttributeExposer
    ATTR_TABLE = category,
